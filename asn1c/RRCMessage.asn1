RRCMessageModule DEFINITIONS AUTOMATIC TAGS ::= 
BEGIN

RRCMessage ::=     SEQUENCE {
    messid      ID,
   data      BIT STRING (SIZE (128))
}

ID ::=     ENUMERATED {rrcSetupRequest, rrcSetup, rrcSetupComplete}
                                                     
END
